module exec {
  yang-version "1";

  namespace "urn:ietf:params:xml:ns:yang:zebra";
  prefix "exec";

  import ietf-inet-types {
    prefix inet;
  }

  import extension {
    prefix ext;
  }

  leaf help {
    ext:help "Show help";
    type empty;
  }

  leaf configure {
    ext:help "Manipulate software configuration information";
    type empty;
  }

  // Temporarily disabled: the authorization framework (role tiers,
  // task groups, enable/disable semantics) is still being designed.
  // The vty shell's enable()/disable() bash functions remain functional
  // because they go through the dedicated Enable/Disable RPCs, not
  // DoExec. Re-enable these leaves once the model is settled.
  /*
  leaf enable {
    ext:help "Promote this session to the admin role (PAM auth)";
    type empty;
  }

  leaf disable {
    ext:help "Drop this session back to the view role";
    type empty;
  }
  */

  // IPv4/IPv6 unicast Loc-RIB selectors shared by the default-VRF
  // `show bgp …` tree and the per-VRF `show bgp vrf <name> …` tree. A
  // bare address does a longest-match lookup; a prefix matches exactly;
  // `longer-prefix` widens it to equal-or-more-specific.
  grouping bgp-show-afi-rib {
    list ipv4 {
      ext:help "BGP IPv4 unicast RIB";
      ext:presence "BGP IPv4 unicast RIB (all prefixes)";
      key value;
      leaf value {
        ext:help "Address (routes containing it), prefix (exact match) or summary";
        // A bare address does a longest-match lookup (routes that
        // contain it); a prefix matches exactly. The handler tells
        // them apart by the presence of `/M`. `summary` rides the key
        // union as an inline enumeration arm because the parser's
        // list position only matches the key — an enum arm is how a
        // keyword lives at the key position (`show bgp ipv4
        // summary`); the handler dispatches on the literal value.
        type union {
          type inet:ipv4-address;
          type inet:ipv4-prefix;
          type enumeration {
            enum summary;
          }
        }
      }
      leaf longer-prefix {
        ext:help "Prefixes equal to or more specific than the given prefix";
        type empty;
      }
    }
    list ipv6 {
      ext:help "BGP IPv6 unicast RIB";
      ext:presence "BGP IPv6 unicast RIB (all prefixes)";
      key value;
      leaf value {
        ext:help "Address (routes containing it), prefix (exact match) or summary";
        type union {
          type inet:ipv6-address;
          type inet:ipv6-prefix;
          type enumeration {
            enum summary;
          }
        }
      }
      leaf longer-prefix {
        ext:help "Prefixes equal to or more specific than the given prefix";
        type empty;
      }
    }
  }

  container show {
    ext:help "Show command";
    presence "Show command";
    leaf version {
      ext:help "Show version";
      type empty;
    }
    leaf router-id {
      ext:help "Show the effective global router ID";
      type empty;
    }
    container candidate-config {
      ext:help "Show the candidate configuration (uncommitted edits)";
      presence "Show candidate config";
      leaf formal {
        ext:help "Set-style flat statement listing";
        type empty;
      }
      leaf json {
        ext:help "Pretty-printed JSON";
        type empty;
      }
      leaf yaml {
        ext:help "YAML";
        type empty;
      }
    }
    container running-config {
      ext:help "Show the running (committed) configuration";
      presence "Show running config";
      leaf formal {
        ext:help "Set-style flat statement listing";
        type empty;
      }
      leaf json {
        ext:help "Pretty-printed JSON";
        type empty;
      }
      leaf yaml {
        ext:help "YAML";
        type empty;
      }
    }
    container mpls {
      ext:help "MPLS forwarding information";
      leaf ilm {
        ext:help "MPLS incoming label map (ILM)";
        type empty;
      }
    }
    leaf nexthop {
      ext:help "Show nexthop group";
      type empty;
    }
    leaf vrf {
      ext:help "Show VRF table";
      type empty;
    }
    leaf task {
      ext:help "Show spawned protocol tasks and their VRF";
      type empty;
    }
    container l2 {
      ext:help "Show L2 / data-link information";
      presence "Show L2";
      leaf neighbor {
        ext:help "Show bridge FDB entries";
        type empty;
      }
      container mac {
        ext:help "Show bridge MAC information";
        leaf table {
          ext:help "Show bridge MAC table (EVPN VNI-keyed)";
          type empty;
        }
      }
    }
    container "community-set" {
      ext:help "Show community-set";
      presence "Show community-set";
      list name {
        ext:help "A named community-set";
        key name;
        leaf name {
          ext:help "Community-set name";
          type string;
        }
      }
    }
    container "ext-community-set" {
      ext:help "Show ext-community-set";
      presence "Show ext-community-set";
      list name {
        ext:help "A named ext-community-set";
        key name;
        leaf name {
          ext:help "Ext-community-set name";
          type string;
        }
      }
    }
    container "large-community-set" {
      ext:help "Show large-community-set";
      presence "Show large-community-set";
      list name {
        ext:help "A named large-community-set";
        key name;
        leaf name {
          ext:help "Large-community-set name";
          type string;
        }
      }
    }
    container "as-path-set" {
      ext:help "Show as-path-set";
      presence "Show as-path-set";
      list name {
        ext:help "A named as-path-set";
        key name;
        leaf name {
          ext:help "As-path-set name";
          type string;
        }
      }
    }
    container "key-chains" {
      ext:help "Show key-chains";
      presence "Show key-chains";
      list name {
        ext:help "A named key-chain";
        key name;
        leaf name {
          ext:help "Key-chain name";
          type string;
        }
      }
    }
    list interface {
      ext:help "Show interface commands";
      ext:presence "Show presence";
      key "if-name-brief";
      leaf if-name-brief {
        ext:help "Interface name";
        ext:dynamic "rib:interface";
        type string;
      }
      leaf detail {
        ext:help "Interface detail";
        type empty;
      }
    }
    leaf hostname {
      ext:help "System host name";
      type empty;
      description
        "The name of the host.  This name can be a single domain
        label or the fully qualified domain name of the host.";
    }
    container evpn {
      ext:help "EVPN information";
      container vni {
        ext:help "EVPN VNI information";
        leaf all {
          ext:help "All EVPN VNIs";
          type empty;
        }
      }
    }
    container bfd {
      ext:help "BFD (Bidirectional Forwarding Detection) information";
      presence "Show BFD session summary";
      list peers {
        ext:help "BFD peer (session) detail";
        ext:presence "Show every peer in detail, or one peer when an address follows";
        key address;
        leaf address {
          ext:help "Peer IP address (IPv4 or IPv6)";
          type inet:ip-address;
        }
      }
      leaf counters {
        ext:help "Per-session control-packet counters";
        type empty;
      }
    }
    container stamp {
      ext:help "STAMP (RFC 8762) link delay measurement";
      presence "Show STAMP session summary";
      leaf session {
        ext:help "Per-session detail";
        type empty;
      }
      leaf statistics {
        ext:help "Sender and reflector packet counters";
        type empty;
      }
    }
    container ebpf {
      ext:help "eBPF data-plane engine (managed cradle) status";
      presence "Show the engine supervisor and port status";
      leaf l2 {
        ext:help "Engine L2 FDB (MAC table)";
        type empty;
      }
      container ipv4 {
        ext:help "Engine IPv4 FIB";
        presence "Show the global-table IPv4 FIB";
        leaf vrf {
          ext:help "Per-VRF FIB (by VRF name)";
          ext:dynamic "rib:vrf";
          type string;
        }
      }
      container ipv6 {
        ext:help "Engine IPv6 FIB";
        presence "Show the global-table IPv6 FIB";
        leaf vrf {
          ext:help "Per-VRF FIB (by VRF name)";
          ext:dynamic "rib:vrf";
          type string;
        }
      }
      leaf mpls {
        ext:help "Engine MPLS ILM (incoming-label map)";
        type empty;
      }
      leaf srv6 {
        ext:help "Engine SRv6 local SIDs and transit encaps";
        type empty;
      }
      leaf nexthop {
        ext:help "Engine nexthops and ECMP groups";
        type empty;
      }
      leaf stats {
        ext:help "Engine datapath packet counters";
        type empty;
      }
    }
    container bgp {
      ext:help "BGP information";
      // `show bgp` with no AFI keyword is IPv4 unicast. A bare address
      // or prefix typed straight after `bgp` (`show bgp A.B.C.D`) is
      // routed into `ipv4` by the matcher via `ext:default-child`.
      ext:default-child "ipv4";
      presence "BGP IPv4 unicast RIB (same as `show bgp ipv4`)";
      // Neighbor summary, one section per AFI/SAFI configured on at
      // least one neighbor. The per-AFI forms (`show bgp ipv4
      // summary`, `show bgp vpnv4 summary`, …) render one section
      // with only the neighbors that have that AFI/SAFI enabled.
      leaf summary {
        ext:help "Summary of BGP neighbor status per AFI/SAFI";
        type empty;
      }
      list neighbor {
        ext:help "BGP neighbor information";
        ext:presence "BGP all neighbor information";
        key name;
        leaf name {
          ext:help "Neighbor address or interface";
          ext:dynamic "bgp:neighbor";
          // Accept either address family (peers are keyed by
          // `IpAddr`) or an `interface-neighbor` name — IPv6
          // unnumbered peers are keyed by interface, so the name is
          // their only typeable identity. The string arm is
          // pattern-less on purpose: a bare string word-matches one
          // token (a pattern would full-match the remaining LINE and
          // break `neighbor i1 advertised-routes`). Address inputs
          // tie the string arm (both Partial), which is safe: the
          // parser folds a union's arms into a single match
          // candidate, and the consumed token is the same either
          // way.
          type union {
            type inet:ipv4-address;
            type inet:ipv6-address;
            type string;
          }
        }
        leaf rtcv4 {
          ext:help "Route Target Constraint (RTC) routes";
          type empty;
        }
        container advertised-routes {
          ext:help "Advertised routes (Adj-RIB-Out)";
          presence "";
          leaf ipv6 {
            ext:help "IPv6 unicast Adj-RIB-Out";
            type empty;
          }
          leaf vpnv4 {
            ext:help "VPNv4 Adj-RIB-Out";
            type empty;
          }
          leaf evpn {
            ext:help "EVPN Adj-RIB-Out";
            type empty;
          }
        }
        container received-routes {
          ext:help "Received routes (Adj-RIB-In)";
          presence "";
          leaf ipv6 {
            ext:help "IPv6 unicast Adj-RIB-In";
            type empty;
          }
          leaf vpnv4 {
            ext:help "VPNv4 Adj-RIB-In";
            type empty;
          }
          leaf evpn {
            ext:help "EVPN Adj-RIB-In";
            type empty;
          }
        }
      }
      uses bgp-show-afi-rib;
      // VPNv4 (SAFI 128) Loc-RIB across every route distinguisher.
      // Mirrors the `ipv4` list above: a bare address after `vpnv4`
      // does a longest-match lookup inside each RD's table; a prefix
      // matches exactly.
      list vpnv4 {
        ext:help "BGP VPNv4 RIB";
        ext:presence "BGP VPNv4 RIB (all route distinguishers)";
        key value;
        leaf value {
          ext:help "Address (routes containing it), prefix (exact match) or summary";
          type union {
            type inet:ipv4-address;
            type inet:ipv4-prefix;
            type enumeration {
              enum summary;
            }
          }
        }
      }
      // VPNv6 (SAFI 128) Loc-RIB across every route distinguisher — the
      // v6 twin of `vpnv4` above.
      list vpnv6 {
        ext:help "BGP VPNv6 RIB";
        ext:presence "BGP VPNv6 RIB (all route distinguishers)";
        key value;
        leaf value {
          ext:help "Address (routes containing it), prefix (exact match) or summary";
          type union {
            type inet:ipv6-address;
            type inet:ipv6-prefix;
            type enumeration {
              enum summary;
            }
          }
        }
      }
      container evpn {
        ext:help "BGP EVPN RIB";
        presence "BGP EVPN RIB";
        leaf summary {
          ext:help "Summary of EVPN-enabled neighbors";
          type empty;
        }
        leaf ethernet-segment {
          ext:help "Locally-configured EVPN Ethernet Segments (RFC 7432)";
          type empty;
        }
        leaf vpws {
          ext:help "EVPN VPWS E-Line services (RFC 8214)";
          type empty;
        }
        leaf route-type {
          ext:help "Filter the EVPN RIB by route type";
          // ethernet-ad=1, macip=2, multicast=3, ethernet-segment=4,
          // prefix=5 (RFC 7432/9136); smet=6, igmp-join-sync=7,
          // igmp-leave-sync=8 (RFC 9251); per-region-imet=9, s-pmsi=10,
          // leaf=11 (RFC 9572).
          type enumeration {
            enum ethernet-ad;
            enum macip;
            enum multicast;
            enum ethernet-segment;
            enum prefix;
            enum smet;
            enum igmp-join-sync;
            enum igmp-leave-sync;
            enum per-region-imet;
            enum s-pmsi;
            enum leaf;
          }
        }
      }
      container mup {
        ext:help "BGP Mobile User Plane (MUP) RIB";
        presence "BGP Mobile User Plane (MUP) RIB";
        leaf summary {
          ext:help "Summary of MUP-enabled neighbors";
          type empty;
        }
      }
      container mup-c {
        ext:help "MUP Controller (MUP-C) status";
        presence "MUP Controller (MUP-C) status";
        leaf session {
          ext:help "Learned PFCP sessions";
          type empty;
        }
        leaf association {
          ext:help "PFCP associations";
          type empty;
        }
      }
      list update-group {
        ext:help "BGP update-groups (IOS-XR style)";
        ext:presence "BGP update-group summary";
        key id;
        leaf id {
          ext:help "Update-group ID, e.g. ipv4-unicast.0";
          ext:dynamic "bgp:update-group";
          type string;
        }
      }
      leaf labeled-unicast {
        ext:help "BGP Labeled-Unicast (SAFI 4) RIB";
        type empty;
      }
      container flowspec {
        ext:help "BGP IPv4 Flow Specification RIB";
        presence "BGP IPv4 Flowspec RIB";
        leaf ipv6 {
          ext:help "BGP IPv6 Flow Specification RIB";
          type empty;
        }
      }
      container sr-policy {
        ext:help "BGP IPv4 SR Policy (SAFI 73) RIB";
        presence "BGP IPv4 SR Policy RIB";
        leaf ipv6 {
          ext:help "BGP IPv6 SR Policy (SAFI 73) RIB";
          type empty;
        }
      }
      leaf link-state {
        ext:help "BGP Link-State (SAFI 71) RIB";
        type empty;
      }
      leaf attributes {
        ext:help "BGP path attribute table";
        type empty;
      }
      list neighbor-group {
        ext:help "BGP neighbor-group inheritance state";
        ext:presence "Show every configured neighbor-group";
        key name;
        leaf name {
          ext:help "Neighbor-group name";
          ext:dynamic "bgp:neighbor-group";
          type string;
        }
      }
      list vrf {
        ext:help "Per-VRF BGP RIB";
        ext:presence "BGP per-VRF summary table";
        // Same positional shortcut as the parent `bgp` container: a
        // bare address/prefix after the VRF name (`show bgp vrf X
        // A.B.C.D`) is routed into this list's `ipv4` child. The
        // matcher applies `ext:default-child` after a list key is
        // matched as well as on a plain container.
        ext:default-child "ipv4";
        key name;
        leaf name {
          ext:help "VRF name";
          ext:dynamic "rib:vrf";
          type string;
        }
        leaf summary {
          ext:help "Summary of this VRF's BGP neighbor status";
          type empty;
        }
        list neighbor {
          ext:help "Detailed information on this VRF's BGP neighbors";
          ext:presence "Detailed information on every neighbor in this VRF";
          key address;
          leaf address {
            ext:help "Neighbor IPv4 or IPv6 address";
            type inet:ip-address;
          }
        }
        leaf mup {
          ext:help "This VRF's BGP Mobile User Plane (MUP) RIB";
          type empty;
        }
        uses bgp-show-afi-rib;
      }
    }
    container ip {
      ext:help "Show IP commands";
      container route {
        ext:help "IPv4 routing table";
        presence "Show IPv4 routes";
        // A bare address or prefix typed straight after `route` lands
        // in the positional-only `prefix` list below — the `show bgp
        // A.B.C.D` UX. There is no keyword spelling: the old `show ip
        // route prefix A.B.C.D/M` form was removed.
        ext:default-child "prefix";
        leaf detail {
          ext:help "Show all routes in detail format (IOS-XR style)";
          type empty;
        }
        list prefix {
          ext:help "Filter to one route";
          ext:positional "show ip route {<A.B.C.D>|<A.B.C.D/M>}";
          key value;
          leaf value {
            ext:help "Address (longest match) or prefix (exact match)";
            type union {
              type inet:ipv4-address;
              type inet:ipv4-prefix;
            }
          }
        }
        list vrf {
          ext:help "IPv4 routing table for a VRF";
          ext:presence "Show every VRF's IPv4 routes";
          // A bare address or prefix after the VRF name filters to one
          // route — the same positional UX as `show ip route <value>`.
          ext:default-child "prefix";
          key name;
          leaf name {
            ext:help "VRF name";
            ext:dynamic "rib:vrf";
            type string;
          }
          leaf detail {
            ext:help "Show this VRF's routes in detail format";
            type empty;
          }
          list prefix {
            ext:help "Filter to one route";
            ext:positional "show ip route vrf <name> {<A.B.C.D>|<A.B.C.D/M>}";
            key value;
            leaf value {
              ext:help "Address (longest match) or prefix (exact match)";
              type union {
                type inet:ipv4-address;
                type inet:ipv4-prefix;
              }
            }
          }
        }
      }
    }

    container ospf {
      ext:help "OSPF commands";
      presence "OSPF instance";
      leaf interface {
        ext:help "OSPF interface";
        type empty;
      }
      container neighbor {
        ext:help "OSPF neighbor";
        presence "OSPF neighbor";
        leaf detail {
          ext:help "OSPF neighbor detail";
          type empty;
        }
      }
      container database {
        ext:help "OSPF database";
        presence "OSPF ddtabase";
        leaf detail {
          ext:help "OSPF database detail";
          type empty;
        }
      }
      leaf route {
        ext:help "OSPF routes";
        type empty;
      }
      leaf graph {
        ext:help "OSPF topology graph";
        type empty;
      }
      leaf spf {
        ext:help "OSPF SPF results";
        type empty;
      }
      leaf ti-lfa {
        ext:help "OSPF TI-LFA per-destination repair paths (graph-level view)";
        type empty;
      }
      container repair-list {
        ext:help "OSPF TI-LFA repair-list";
        presence "OSPF repair-list";
        leaf detail {
          ext:help "OSPF repair-list detail (per-segment label breakdown)";
          type empty;
        }
      }
      leaf flex-algo {
        ext:help "OSPF Flexible Algorithm (RFC 9350) state";
        type empty;
      }
      leaf segment-routing {
        ext:help "OSPF Segment Routing state";
        type empty;
      }
      leaf graceful-restart {
        ext:help "OSPF graceful-restart helper status";
        type empty;
      }
      leaf checkpoint {
        ext:help "OSPF graceful-restart checkpoint (on-disk state)";
        type empty;
      }
      list vrf {
        // Per-VRF OSPFv2 show. `show ospf vrf <name> <cmd>` is
        // redirected by the config manager (it strips the
        // `vrf <name>` selector via `vrf_redirect_split`) into the
        // per-VRF task's show channel registered as
        // `"ospf:vrf:<name>"`. The stripped command renders via the
        // child's existing handlers; a bare `... vrf <name>` maps to
        // the summary (`show ospf`).
        ext:help "Per-VRF OSPFv2 instance";
        ext:presence "Show this VRF's OSPFv2 summary";
        key name;
        leaf name {
          ext:help "VRF name";
          ext:dynamic "rib:vrf";
          type string;
        }
        leaf interface {
          ext:help "OSPF interfaces in this VRF";
          type empty;
        }
        container neighbor {
          ext:help "OSPF neighbors in this VRF";
          presence "OSPF neighbor";
          leaf detail {
            ext:help "OSPF neighbor detail in this VRF";
            type empty;
          }
        }
        container database {
          ext:help "OSPF database in this VRF";
          presence "OSPF database";
          leaf detail {
            ext:help "OSPF database detail in this VRF";
            type empty;
          }
        }
        leaf route {
          ext:help "OSPF routes in this VRF";
          type empty;
        }
      }
    }

    container isis {
      ext:help "IS-IS commands";
      presence "IS-IS instance";
      leaf summary {
        ext:help "IS-IS summary";
        type empty;
      }
      container route {
        ext:help "IS-IS route";
        presence "Show IS-IS routes";
        leaf detail {
          ext:help "Show IS-IS routes in detail format (TI-LFA, SR-MPLS, SRv6)";
          type empty;
        }
      }
      container fast-reroute {
        ext:help "IS-IS Fast ReRoute (TI-LFA) information";
        presence "Show TI-LFA information";
        leaf summary {
          ext:help "Per-level counters: protected / unprotected prefixes";
          type empty;
        }
        list prefix {
          ext:help "Per-prefix TI-LFA repair detail";
          ext:presence "Show TI-LFA repair detail for one prefix";
          key value;
          leaf value {
            ext:help "IPv4 prefix (A.B.C.D/M)";
            type inet:ipv4-prefix;
          }
          leaf detail {
            ext:help "Detail format (P/Q nodes, segment list, backup-src)";
            type empty;
          }
        }
      }
      leaf egress-protection {
        ext:help "Mirror SID egress-protection entries (SRv6/SR-MPLS)";
        type empty;
      }
      container interface {
        ext:help "IS-IS interface";
        presence "IS-IS interface";
        leaf detail {
          ext:help "IS-IS interface detail";
          type empty;
        }
      }
      container dis {
        ext:help "IS-IS DIS election";
        leaf statistics {
          ext:help "DIS election statistics";
          type empty;
        }
        leaf history {
          ext:help "DIS election history";
          type empty;
        }
      }
      leaf graph {
        ext:help "IS-IS topology graph";
        type empty;
      }
      container spf {
        ext:help "IS-IS SPF";
        presence "IS-IS SPF";
        leaf detail {
          ext:help "IS-IS SPF detail (per-destination paths, TI-LFA repair info)";
          type empty;
        }
      }
      container repair-list {
        ext:help "IS-IS TI-LFA repair-list";
        presence "IS-IS repair-list";
        leaf detail {
          ext:help "IS-IS repair-list detail (per-segment NodeSID/AdjSID breakdown)";
          type empty;
        }
      }
      leaf ti-lfa {
        ext:help "IS-IS TI-LFA per-destination repair paths (graph-level view)";
        type empty;
      }
      leaf topology {
        ext:help "IS-IS SPF tree (per-AFI today; per-MT once multi-topology lands)";
        type empty;
      }
      container neighbor {
        ext:help "IS-IS neighbor";
        presence "IS-IS neighbor";
        leaf detail {
          ext:help "IS-IS neighbor detail";
          type empty;
        }
      }
      leaf graceful-restart {
        ext:help "IS-IS Graceful Restart (RFC 5306) per-adjacency observation";
        type empty;
      }
      leaf checkpoint {
        ext:help "IS-IS graceful-restart checkpoint (on-disk state)";
        type empty;
      }
      leaf hostname {
        ext:help "IS-IS hostname";
        type empty;
      }
      container database {
        ext:help "IS-IS database";
        presence "IS-IS database";
        leaf detail {
          ext:help "IS-IS database detail";
          type empty;
        }
      }
      container flex-algo {
        ext:help "IS-IS Flexible Algorithm (RFC 9350)";
        presence "Show flex-algo state";
        // A bare algorithm id typed straight after `flex-algo` lands in
        // the positional-only `algorithm` list below, so every per-algo
        // view hangs off one namespace:
        //
        //   show isis flex-algo 128            <- FAD + participation
        //   show isis flex-algo 128 topology   <- algo-N SPF tree
        //   show isis flex-algo 128 route      <- algo-N RIB
        //   show isis flex-algo 128 spf        <- algo-N SPF result
        //   show isis flex-algo 128 graph      <- algo-N pruned graph
        //
        // The un-suffixed `show isis spf|graph|topology` stay algorithm-0
        // views. Keeping the algorithm id adjacent to `flex-algo` (rather
        // than bolting an `algorithm N` modifier onto five unrelated
        // commands) is a deliberate house choice; IOS-XR/Juniper/FRR all
        // spell it as a trailing modifier instead.
        ext:default-child "algorithm";

        list algorithm {
          ext:help "Filter to one Flex-Algorithm";
          ext:positional "show isis flex-algo <128-255>";
          key value;
          leaf value {
            ext:help "Algorithm ID (128-255)";
            type uint8 {
              range "128..255";
            }
          }
          leaf topology {
            ext:help "SPF tree computed for this algorithm";
            type empty;
          }
          leaf route {
            ext:help "IPv4 RIB computed for this algorithm";
            type empty;
          }
          leaf spf {
            ext:help "SPF result (per-destination paths) for this algorithm";
            type empty;
          }
          leaf graph {
            ext:help "Constrained topology graph for this algorithm";
            type empty;
          }
          leaf repair-list {
            ext:help "TI-LFA repair paths computed for this algorithm";
            type empty;
          }
        }

        container route {
          ext:help "Per-algorithm IPv4 RIB (all algorithms)";
          presence "Show flex-algo per-algo routes";
          list algorithm {
            // Deprecated spelling. `show isis flex-algo 128 route` is the
            // supported form; this one predates the per-algo namespace and
            // is kept so existing scripts keep parsing.
            ext:help "Filter to a specific algorithm id (deprecated)";
            ext:presence "Show flex-algo routes for one algorithm";
            key value;
            leaf value {
              ext:help "Algorithm ID (0-255)";
              type uint8;
            }
          }
        }
      }

      list vrf {
        // Per-VRF IS-IS instance show. `show isis vrf <name> <cmd>` is
        // redirected by the config manager (it strips the `vrf <name>`
        // selector via `vrf_redirect_split`) into the per-VRF task's
        // show channel registered as `"isis:vrf:<name>"`. The stripped
        // command (`show isis <cmd>`) is rendered by the child's
        // existing show handlers, so this list mirrors a subset of the
        // top-level leaves above.
        ext:help "Per-VRF IS-IS instance";
        key name;
        leaf name {
          ext:help "VRF name";
          ext:dynamic "rib:vrf";
          type string;
        }
        leaf summary {
          ext:help "IS-IS summary for this VRF";
          type empty;
        }
        leaf neighbor {
          ext:help "IS-IS neighbors in this VRF";
          type empty;
        }
        leaf database {
          ext:help "IS-IS database for this VRF";
          type empty;
        }
        leaf route {
          ext:help "IS-IS routes in this VRF";
          type empty;
        }
        leaf interface {
          ext:help "IS-IS interfaces in this VRF";
          type empty;
        }
        leaf topology {
          ext:help "IS-IS SPF tree for this VRF";
          type empty;
        }
      }
    }
    container ipv6 {
      ext:help "Show IPv6 commands";
      container route {
        ext:help "IPv6 routing table";
        presence "Show IPv6 routes";
        // Positional address/prefix filter — the v6 twin of `show ip
        // route` above.
        ext:default-child "prefix";
        leaf detail {
          ext:help "Show all routes in detail format (IOS-XR style)";
          type empty;
        }
        list prefix {
          ext:help "Filter to one route";
          ext:positional "show ipv6 route {<X:X::X:X>|<X:X::X:X/M>}";
          key value;
          leaf value {
            ext:help "Address (longest match) or prefix (exact match)";
            type union {
              type inet:ipv6-address;
              type inet:ipv6-prefix;
            }
          }
        }
        list vrf {
          ext:help "IPv6 routing table for a VRF";
          ext:presence "Show every VRF's IPv6 routes";
          // Positional single-route filter — the v6 twin of the
          // `show ip route vrf` list above.
          ext:default-child "prefix";
          key name;
          leaf name {
            ext:help "VRF name";
            ext:dynamic "rib:vrf";
            type string;
          }
          leaf detail {
            ext:help "Show this VRF's routes in detail format";
            type empty;
          }
          list prefix {
            ext:help "Filter to one route";
            ext:positional "show ipv6 route vrf <name> {<X:X::X:X>|<X:X::X:X/M>}";
            key value;
            leaf value {
              ext:help "Address (longest match) or prefix (exact match)";
              type union {
                type inet:ipv6-address;
                type inet:ipv6-prefix;
              }
            }
          }
        }
      }
      container nd {
        ext:help "IPv6 neighbor discovery";
        presence "Show IPv6 ND status";
        list interface {
          ext:help "ND status per interface";
          ext:presence "Show all interfaces";
          key if-name;
          leaf if-name {
            ext:help "Interface name";
            ext:dynamic "rib:interface";
            type string;
          }
        }
      }
    }

    container igmp {
      ext:help "IGMP commands";
      presence "IGMP status";
      container interface {
        ext:help "IGMP interface and querier state";
        presence "IGMP interface";
      }
      container groups {
        ext:help "IGMP group membership";
        presence "IGMP groups";
      }
      list vrf {
        ext:help "Per-VRF IGMP state";
        key name;
        leaf name {
          ext:help "VRF name";
          ext:dynamic "rib:vrf";
          type string;
        }
        leaf interface {
          ext:help "IGMP interfaces in this VRF";
          type empty;
        }
        leaf groups {
          ext:help "IGMP groups in this VRF";
          type empty;
        }
      }
    }

    container pim {
      ext:help "PIM commands";
      presence "PIM instance";
      container interface {
        ext:help "PIM interface";
        presence "PIM interface";
      }
      container neighbor {
        ext:help "PIM neighbor";
        presence "PIM neighbor";
      }
      container upstream {
        ext:help "PIM upstream (S,G) join state";
        presence "PIM upstream";
      }
      container rp-info {
        ext:help "PIM group-to-RP mappings";
        presence "PIM RP info";
      }
      container bsr {
        ext:help "Bootstrap Router state";
        presence "PIM BSR";
      }
      container assert {
        ext:help "PIM assert election state";
        presence "PIM assert";
      }
      container ipv6 {
        // PIMv6 show: the default `router pim` task strips the `ipv6`
        // container and forwards to the default-table Pim<Ipv6> child.
        ext:help "PIMv6 (IPv6) state";
        presence "PIMv6";
        container interface {
          ext:help "PIMv6 interface";
          presence "PIMv6 interface";
        }
        container neighbor {
          ext:help "PIMv6 neighbor";
          presence "PIMv6 neighbor";
        }
        container upstream {
          ext:help "PIMv6 upstream (S,G) join state";
          presence "PIMv6 upstream";
        }
        container mroute {
          ext:help "PIMv6 multicast routing table (MRT6 MFC)";
          presence "PIMv6 mroute";
        }
        container assert {
          ext:help "PIMv6 assert election state";
          presence "PIMv6 assert";
        }
        container bsr {
          ext:help "PIMv6 Bootstrap Router state";
          presence "PIMv6 BSR";
        }
        container rp-info {
          ext:help "PIMv6 group-to-RP mappings";
          presence "PIMv6 RP info";
        }
        container mld {
          ext:help "MLD membership state";
          container interface {
            ext:help "MLD interface (querier) state";
            presence "MLD interface";
          }
          container groups {
            ext:help "MLD group memberships";
            presence "MLD groups";
          }
        }
      }
      list vrf {
        // Per-VRF PIM show: the manager strips the `vrf <name>`
        // selector (vrf_redirect_split) and redirects into the child
        // registered as "pim:vrf:<name>".
        ext:help "Per-VRF PIM instance";
        key name;
        leaf name {
          ext:help "VRF name";
          ext:dynamic "rib:vrf";
          type string;
        }
        leaf interface {
          ext:help "PIM interfaces in this VRF";
          type empty;
        }
        leaf neighbor {
          ext:help "PIM neighbors in this VRF";
          type empty;
        }
        leaf upstream {
          ext:help "PIM upstream state in this VRF";
          type empty;
        }
        leaf rp-info {
          ext:help "Group-to-RP mappings in this VRF";
          type empty;
        }
        leaf assert {
          ext:help "Assert state in this VRF";
          type empty;
        }
        container ipv6 {
          ext:help "PIMv6 (IPv6) state in this VRF";
          presence "PIMv6 in this VRF";
          container interface {
            ext:help "PIMv6 interface";
            presence "PIMv6 interface";
          }
          container neighbor {
            ext:help "PIMv6 neighbor";
            presence "PIMv6 neighbor";
          }
          container upstream {
            ext:help "PIMv6 upstream (S,G) join state";
            presence "PIMv6 upstream";
          }
          container mroute {
            ext:help "PIMv6 multicast routing table (MRT6 MFC)";
            presence "PIMv6 mroute";
          }
          container assert {
            ext:help "PIMv6 assert election state";
            presence "PIMv6 assert";
          }
          container rp-info {
            ext:help "PIMv6 group-to-RP mappings";
            presence "PIMv6 RP info";
          }
          container mld {
            ext:help "MLD membership state";
            container interface {
              ext:help "MLD interface (querier) state";
              presence "MLD interface";
            }
            container groups {
              ext:help "MLD group memberships";
              presence "MLD groups";
            }
          }
        }
      }
    }

    container mroute {
      ext:help "IP multicast routing table";
      presence "Multicast routes";
      list vrf {
        ext:help "Multicast routes in a VRF";
        key name;
        leaf name {
          ext:help "VRF name";
          ext:dynamic "rib:vrf";
          type string;
        }
      }
    }

    container ospfv3 {
      ext:help "OSPFv3 commands";
      presence "OSPFv3 instance";
      leaf interface {
        ext:help "OSPFv3 interface";
        type empty;
      }
      container neighbor {
        ext:help "OSPFv3 neighbor";
        presence "OSPFv3 neighbor";
        leaf detail {
          ext:help "OSPFv3 neighbor detail";
          type empty;
        }
      }
      container database {
        ext:help "OSPFv3 LSDB";
        presence "OSPFv3 LSDB";
        leaf detail {
          ext:help "OSPFv3 LSDB detail";
          type empty;
        }
      }
      leaf route {
        ext:help "OSPFv3 routes";
        type empty;
      }
      leaf graph {
        ext:help "OSPFv3 topology graph";
        type empty;
      }
      leaf spf {
        ext:help "OSPFv3 SPF results";
        type empty;
      }
      leaf ti-lfa {
        ext:help "OSPFv3 TI-LFA per-destination repair paths (graph-level view)";
        type empty;
      }
      container repair-list {
        ext:help "OSPFv3 TI-LFA repair-list";
        presence "OSPFv3 repair-list";
        leaf detail {
          ext:help "OSPFv3 repair-list detail (per-segment label breakdown)";
          type empty;
        }
      }
      leaf flex-algo {
        ext:help "OSPFv3 Flexible Algorithm (RFC 9350) state";
        type empty;
      }
      leaf segment-routing {
        ext:help "OSPFv3 Segment Routing state";
        type empty;
      }
      leaf srv6 {
        ext:help "Show SRv6 state (locator, End/End.X SIDs)";
        type empty;
      }
      leaf graceful-restart {
        ext:help "OSPFv3 graceful-restart helper/restarter status";
        type empty;
      }
      leaf checkpoint {
        ext:help "OSPFv3 graceful-restart checkpoint (on-disk state)";
        type empty;
      }
      list vrf {
        // Per-VRF OSPFv3 show. `show ospfv3 vrf <name> <cmd>` is
        // redirected by the config manager into the per-VRF task's
        // show channel registered as `"ospfv3:vrf:<name>"`; the
        // stripped command renders via the child's handlers (a bare
        // `... vrf <name>` maps to the summary).
        ext:help "Per-VRF OSPFv3 instance";
        ext:presence "Show this VRF's OSPFv3 summary";
        key name;
        leaf name {
          ext:help "VRF name";
          ext:dynamic "rib:vrf";
          type string;
        }
        leaf interface {
          ext:help "OSPFv3 interfaces in this VRF";
          type empty;
        }
        container neighbor {
          ext:help "OSPFv3 neighbors in this VRF";
          presence "OSPFv3 neighbor";
          leaf detail {
            ext:help "OSPFv3 neighbor detail in this VRF";
            type empty;
          }
        }
        container database {
          ext:help "OSPFv3 database in this VRF";
          presence "OSPFv3 database";
          leaf detail {
            ext:help "OSPFv3 database detail in this VRF";
            type empty;
          }
        }
        leaf route {
          ext:help "OSPFv3 routes in this VRF";
          type empty;
        }
      }
    }
    container "policy" {
      ext:help "Show policy";
      presence "Show policy";
    }
    container segment-routing {
      ext:help "Show segment-routing";
      presence "Segment Routing";
      container srv6 {
        ext:help "Show SRv6";
        presence "SRv6";
        leaf sid {
          ext:help "Show allocated SRv6 SIDs";
          type empty;
        }
      }
    }
    container "prefix-set" {
      ext:help "Show prefix-set";
      presence "Show prefix-set";
      list name {
        ext:help "A named prefix-set";
        key name;
        leaf name {
          ext:help "Prefix-set name";
          type string;
        }
      }
    }
  }
  container cli {
    ext:help "Command line interface";
    leaf format {
      ext:help "CLI output format";
      type enumeration {
        enum terminal {
          description "Terminal output format";
        }
        enum json {
          description "JSON output";
        }
      }
    }
  }
}
